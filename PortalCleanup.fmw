FME workspace PortalCleanup.fmw

Parameters:
- DestDataset_XLSXW = \\PortsmouthNH2\Data\FME\Portal\Users\Output   # Destination Microsoft Excel File
- Portal =   # Enter Portal URL
- Username =   # Enter Username
- Password =   # Enter a Password
- SourceDataset_XLSXR = $(FME_MF_DIR)ExampleUserSheet.xlsx   # Source Microsoft Excel File(s)

Readers:
- XLSXR_1: XLSXR from $(SourceDataset_XLSXR)

Sheet1/Table1 (reader XLSXR_1)
    attributes: Username (Portal) string, Full Name (Portal) string, License Type string, Role string, Groups Owned Count string, Groups Owned List string, Last Login string, Last Login (Pro) string, Termination Date (TAPI) string, Disabled string, Storage Usage (Bytes) string, Account Created string, Account Modified string, Pro Disconnected string, Pro Licenses string, Username (TAPI) string, Full Name (TAPI) string, Location string, Job Title string, Department Code string, Department string, Email string, Supervisor Name string, Supervisor Email string
    -> LicenseType
Note: Filter by License Type (AGE)
LicenseType: AttributeFilter
    ATTR_NAME = License Type
    ATTR_VALUES = <Empty>,<Missing>,<Null>,<Unfiltered>,creatorUT,fieldWorkerUT,viewerUT
    creatorUT -> ProUsers
    fieldWorkerUT -> GroupRemover
    viewerUT -> GroupRemover

Bookmark: CreatorTypes
ProUsers: AttributeFilter
    ATTR_NAME = Pro Licenses
    ATTR_VALUES = <Empty>,<Missing>,<Null>,<Unfiltered>
    <EMPTY> -> contentCount_2
    <MISSING> -> contentCount_2
    <NULL> -> contentCount_2
    <UNFILTERED> -> RevokeLicense
RevokeLicense: PythonCaller
    PYTHONSOURCE:
      import fme
      import fmeobjects
      from arcgis.gis import GIS

      gis = GIS(url=str(FME_MacroValues['Portal']),username=str(FME_MacroValues['Username']),password=str(FME_MacroValues['Password']))

      def license_revoker(feature):
          try:
              pro_license = gis.admin.license.get('ArcGIS Pro')
              pro_license.assign(username=feature.getAttribute('baseusername'), entitlements=[])
          except Exception as e:
              print(e)
    PYTHONSYMBOL = license_revoker
    -> contentCount_2
Note: Check if User owns Content. NOTE: This process is buggy and will return a None type value which is equivalent to NULL. / Need to Fix/Find better way of doing this.
contentCount_2: PythonCaller
    NEW_ATTRIBUTES = contentOwned
    PYTHONSOURCE:
      import fme
      import fmeobjects
      from arcgis.gis import GIS
      gis = GIS(url=str(FME_MacroValues['Portal']),username=str(FME_MacroValues['Username']),password=str(FME_MacroValues['Password']))

      def contentCount(feature):
          qe = f"owner: {feature.getAttribute('baseusername')}"
          content_count = gis.content.advanced_search(query=qe,return_count=True)
          print(content_count)
          feature.setAttribute('contentOwned', content_count)
          return feature
    PYTHONSYMBOL = contentCount
    -> GroupsOwned_2
Note: Check if user owns groups OR content
GroupsOwned_2: Tester
    BOOL_OP = OR
    TEST_CLAUSE:
      TEST @Value(Groups Owned Count) > 0
      TEST @Value(contentOwned) > 0
    TEST_MODE = TEST
    PASSED -> DisableUser
    FAILED -> CheckForNullValues_2
CheckForNullValues_2: Tester
    BOOL_OP = OR
    TEST_CLAUSE:
      TEST contentOwned ATTRIBUTE_VALUE_NULL ""
      TEST Groups Owned Count ATTRIBUTE_VALUE_NULL ""
    TEST_MODE = TEST
    PASSED -> DisableUser
    FAILED -> GroupRemover_2
DisableUser: PythonCaller
    PYTHONSOURCE:
      import fme
      import fmeobjects
      from arcgis.gis import GIS
      gis = GIS(url=str(FME_MacroValues['Portal']),username=str(FME_MacroValues['Username']),password=str(FME_MacroValues['Password']))

      def disableUser(feature):
          try:
              user = gis.users.get(username=feature.getAttribute('baseusername'))
              user.disable()
              #feature.setAttribute('contentOwned', content_count)
              return feature
          except Exception as e:
              print(e)
    PYTHONSYMBOL = disableUser
    -> ManualInterventionTable
Note: Check if user belongs to groups, remove them, return User Object
GroupRemover_2: PythonCaller
    PYTHONSOURCE:
      import fme
      import fmeobjects
      from arcgis.gis import GIS
      gis = GIS(url=str(FME_MacroValues['Portal']),username=str(FME_MacroValues['Username']),password=str(FME_MacroValues['Password']))


      def groupRemover(feature):
          portaluser = gis.users.get(username = feature.getAttribute('baseusername'))
          if portaluser != None:
              user_groups = portaluser.groups
              for group in user_groups:
                  targetgroup = gis.groups.get(group.id)
                  targetgroup.remove_users([portaluser])
          if portaluser == None:
              portaluser = gis.users.get(username = feature.getAttribute('baseusername')+"@terracon.com")
              try:
                  user_groups = portaluser.groups
                  for group in user_groups:
                      targetgroup = gis.groups.get(group.id)
                      targetgroup.remove_users([portaluser])
              except Exception as e:
                  print(e)
    PYTHONSYMBOL = groupRemover
    -> DeleteUser_2
Note: Input User Object, Delete User
DeleteUser_2: PythonCaller
    PYTHONSOURCE:
      import fme
      import fmeobjects
      from arcgis.gis import GIS
      gis = GIS(url=str(FME_MacroValues['Portal']),username=str(FME_MacroValues['Username']),password=str(FME_MacroValues['Password']))

      def deleteUser(feature):
          try:
              portaluser = gis.users.get(username = feature.getAttribute('baseusername'))
              portaluser.delete()
              return feature
          except Exception as e:
              print(e)
    PYTHONSYMBOL = deleteUser
    -> DeletedUsersTable

Bookmark: Users Requiring Manual Intervention
ManualInterventionTable: HTMLReportGenerator
    CONTENT_LIST = HEADER TABLE
    PAGE_CONFIG = HEADER{{TEXT;Users Requiring Manual Intervention ;HEADER;NO;HEADER_ID;;ALIGNMENT;LEFT;COLOR;0,0,0;FME_CONTROLLER_QUERY_FILE;transformers/dependencies/html5/Header.fme;FME_CONTROLLER_CHOICE;Header}}TABLE{{STYLE;BORDERED;TABLE;Full Name (TAPI)|Name/License Type|License/Pro Licenses|Pro?/Supervisor Name|Boss Name/Supervisor Email|Boss Email/Platform|Portal or AGO?/contentOwned|Number of Items/Groups Owned Count|Groups Owned;FME_CONTROLLER_QUERY_FILE;transformers/dependencies/html5/Table.fme;FME_CONTROLLER_CHOICE;Table}}
    TITLE = "Users Requiring Manual Intervention "
    -> HTMLLayouter

Bookmark: Viewers and FieldWorkers
Note: Check if user belongs to groups, remove them, return User Object
GroupRemover: PythonCaller
    PYTHONSOURCE:
      import fme
      import fmeobjects
      from arcgis.gis import GIS
      gis = GIS(url=str(FME_MacroValues['Portal']),username=str(FME_MacroValues['Username']),password=str(FME_MacroValues['Password']))


      def groupRemover(feature):
          portaluser = gis.users.get(username = feature.getAttribute('baseusername'))
          if portaluser != None:
              user_groups = portaluser.groups
              for group in user_groups:
                  targetgroup = gis.groups.get(group.id)
                  targetgroup.remove_users([portaluser])
          if portaluser == None:
              portaluser = gis.users.get(username = feature.getAttribute('baseusername')+"@yourcompany.com")
              try:
                  user_groups = portaluser.groups
                  for group in user_groups:
                      targetgroup = gis.groups.get(group.id)
                      targetgroup.remove_users([portaluser])
              except Exception as e:
                  print(e)
          return feature
    PYTHONSYMBOL = groupRemover
    -> DeleteUser
Note: Input User Object, Delete User
DeleteUser: PythonCaller
    PYTHONSOURCE:
      import fme
      import fmeobjects
      from arcgis.gis import GIS
      gis = GIS(url=str(FME_MacroValues['Portal']),username=str(FME_MacroValues['Username']),password=str(FME_MacroValues['Password']))

      def deleteUser(feature):
          try:
              portaluser = gis.users.get(username = feature.getAttribute('baseusername'))
              portaluser.delete()
          except Exception as e:
              print(e)
    PYTHONSYMBOL = deleteUser
    -> DeletedUsersTable

Bookmark: New Bookmark
DeletedUsersTable: HTMLReportGenerator
    CONTENT_LIST = HEADER TABLE
    PAGE_CONFIG = HEADER{{TEXT;Users Deleted;HEADER;NO;HEADER_ID;;ALIGNMENT;LEFT;COLOR;0,0,0;FME_CONTROLLER_QUERY_FILE;transformers/dependencies/html5/Header.fme;FME_CONTROLLER_CHOICE;Header}}TABLE{{STYLE;BORDERED;TABLE;Full Name (TAPI)|Name/License Type|License/Pro Licenses|Pro?/Supervisor Name|Boss Name/Supervisor Email|Boss Email/Platform|Portal or AGO?/contentOwned|Number of Items/Groups Owned Count|Groups Owned;FME_CONTROLLER_QUERY_FILE;transformers/dependencies/html5/Table.fme;FME_CONTROLLER_CHOICE;Table}}
    TITLE = $(DestDataset_XLSXW)
    -> HTMLLayouter
HTMLLayouter
    DIV_STYLE = SOLID
    LAYOUT = VERTICAL
    -> Emailer
Emailer
    SERVICE = Generic SMTP
    SMTP_CONNECTION = HOST;;PORT;25;ENCRYPTION;None;TIMEOUT;60;AUTHENTICATION;No;USERNAME;<Unused>;PASSWORD;<Unused>;FME_CONTROLLER_QUERY_FILE;"dependencies/Generic SMTP.fme";FME_CONTROLLER_CHOICE;"Generic SMTP"
